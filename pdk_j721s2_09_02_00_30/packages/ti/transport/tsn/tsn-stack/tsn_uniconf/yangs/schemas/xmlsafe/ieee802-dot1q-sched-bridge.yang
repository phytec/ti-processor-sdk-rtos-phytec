module ieee802-dot1q-sched-bridge {
  yang-version 1.1;
  namespace "urn:ieee:std:802.1Q:yang:ieee802-dot1q-sched-bridge";
  prefix sched-bridge;

  import ietf-interfaces {
    prefix if;
  }
  import ieee802-dot1q-bridge {
    prefix dot1q;
  }
  import ieee802-dot1q-sched {
    prefix sched;
  }

  organization
    "IEEE 802.1 Working Group";
  contact
    "WG-URL: http://www.ieee802.org/1/
     WG-EMail: stds-802-1-l@ieee.org

     Contact: IEEE 802.1 Working Group Chair
     Postal: C/O IEEE 802.1 Working Group
     IEEE Standards Association
     445 Hoes Lane
     Piscataway, NJ 08854
     USA

     E-mail: STDS-802-1-CHAIRS@IEEE.ORG";
  description
    "This module provides for management of IEEE Std 802.1Q Bridges that
     support Scheduled Traffic Enhancements.

     Copyright (C) IEEE (2023).

     This version of this YANG module is part of IEEE Std 802.1Q; see the
     standard itself for full legal notices.";

  revision 2023-03-08 {
    description
      "Published as part of IEEE Std 802.1Qcw-2023.

       The following reference statement identifies each referenced IEEE
       Standard as updated by applicable amendments.";
    reference
      "IEEE Std 802.1Q Bridges and Bridged Networks:
       IEEE Stds 802.1Q-2022, 802.1Qcw-2023.";
  }

  augment "/if:interfaces/if:interface/dot1q:bridge-port" {
    description
      "Augment bridge-port with Scheduled Traffic configuration.";
    uses sched:sched-parameters;
  }
}
