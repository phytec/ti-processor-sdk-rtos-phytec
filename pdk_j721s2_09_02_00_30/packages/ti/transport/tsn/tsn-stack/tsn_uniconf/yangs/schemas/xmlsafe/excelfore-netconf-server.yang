module excelfore-netconf-server {
  yang-version 1.1;
  namespace "http://excelfore.com/ns/excelfore-netconf-server";
  prefix xl4nconf;

  import ietf-inet-types {
    prefix inet;
  }
  import ietf-x509-cert-to-name {
    prefix x509c2n;
  }

  description
    "This YANG module to define Excelfore Netconf Server Configurations.";

  revision 2023-08-07 {
    description
      "Initial revision.";
    reference
      "Excelfore netconf server specification";
  }

  container x4nconf-server {
    description
      "Top-level container for Excelfore NETCONF server configuration.";
    container transport {
      container tls {
        leaf port {
          type inet:port-number;
          description
            "Specifies the TCP port to listen for NETCONF over TLS messages.";
          default "6513";
          reference
            "RFC 7589: NETCONF over TLS";
        }
        leaf server-cert {
          type string {
            length "1 .. max";
          }
          mandatory true;
          description
            "Contains path to SSL server X.509 certificate in pem format
             used for the NETCONF over TLS protocol.";
        }
        leaf server-key {
          type string {
            length "1 .. max";
          }
          mandatory true;
          description
            "Contains path to SSL server X.509 certificate key in pem format
             used for the NETCONF over TLS protocol.";
        }
        leaf capath {
          type string {
            length "1 .. max";
          }
          description
            "Contains the path to directory that contains the CA files
             in pem format. If not defined the server will try to check
             CA files located in the system defaults (e.g. '/etc/ssl/certs'
             for linux)";
        }
        uses x509c2n:cert-to-name;
      }
      container ssh {
        leaf port {
          type inet:port-number;
          description
            "Specifies the TCP ports that the server will accept connections from.
             Note: This port must be configured and enabled in the SSH server
             configuration itself (e.g. /etc/ssh/sshd_config in linux)";
          default "830";
          reference
            "RFC 6242: NETCONF over SSH";
        }
        leaf use-unix-domain-socket {
          type boolean;
          description
            "Enable the use of Unix Domain Socket for IPC between the
             SSH subsystem application and the x4nconf daemon instead
             Local TCP Socket";
          default "false";
        }
        leaf sub-ipc-port {
          type inet:port-number;
          description
            "Specifies the TCP ports that the x4nconf daemon will listen
             and accept connections from the SSH subsystem application.
             Not used if 'use-unix-domain-socket' was enabled";
          default "10830";
        }
        leaf sub-socket-name {
          type string {
            length "1 .. max";
          }
          description
            "Unix Domain Socket Name. Used only if 'use-unix-domain-socket-usesunix'
             is enabled";
          default "/tmp/x4nconfsrv.sock";
        }
      }
    }
  }
}
