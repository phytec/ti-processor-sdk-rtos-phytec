module ieee802-dot1q-tsn-config-uni {
  yang-version 1.1;
  namespace "urn:ieee:std:802.1Q:yang:ieee802-dot1q-tsn-config-uni";
  prefix dot1q-tsn-config-uni;

  import ieee802-dot1q-tsn-types {
    prefix tsn;
    reference
      "48.6.3 of IEEE Std 802.1Q-2022";
  }

  organization
    "Institute of Electrical and Electronics Engineers";
  contact
    "WG-URL: http://ieee802.org/1/
     WG-EMail: stds-802-1-l@ieee.org

     Contact: IEEE 802.1 Working Group Chair
     Postal: C/O IEEE 802.1 Working Group
          IEEE Standards Association
          445 Hoes Lane
          Piscataway, NJ 08854
          USA

     E-mail: stds-802-1-chairs@ieee.org";
  description
    "Time-Sensitive Networking (TSN) User/Network Interface (UNI) for the
     exchange of information between CUC and CNC that are required to
     configure TSN Streams in a TSN network.";

  revision 2023-05-16 {
    description
      "Editor's note: this revision statement will be removed prior to
       publication. It is only present while the project is running in
       order to make it easier for the reader to see what changes have
       been introduced while the project is running. Update for D1.1 that
       includes fixes, and updates and adds RPCs, actions, and
       notifications.";
    reference
      "Clause 46.2 of IEEE Std 802.1Q-2022";
  }
  revision 2022-11-09 {
    description
      "Editor's note: this revision statement will be removed prior to
       publication. It is only present while the project is running in
       order to make it easier for the reader to see what changes have
       been introduced while the project is running. Update for D1.0 that
       rebases the YANG module of IEEE Std 802.1Q-2022 and updates RPCs,
       actions, and notifications.";
    reference
      "Clause 46.2 of IEEE Std 802.1Q-2022";
  }
  revision 2022-06-03 {
    description
      "Editor's note: this revision statement will be removed prior to
       publication. It is only present while the project is running in
       order to make it easier for the reader to see what changes have
       been introduced while the project is running. Update for D0.3 that
       restructures the data model, adds RPCS, adds actions, and adds
       notifications.";
    reference
      "Clause 46.2 of IEEE Std 802.1Qcc-2018";
  }
  revision 2021-12-16 {
    description
      "Initial revision. Note that this module might change in backward
       incompatible ways until approved as a standard.";
    reference
      "Clause 46.2 of IEEE Std 802.1Q-2022";
  }

  container tsn-uni {
    description
      "Top-level container for the TSN UNI module.";
    list domain {
      key "domain-id";
      description
        "List of Configuration Domains.

         This list exists so CUCs can be associated with the Configuration
         Domain they are located in and can be used to restrict access to
         CUCs, e.g., by using standard mechanism as described in RFC 8341.";
      leaf domain-id {
        type string;
        description
          "The Domain ID is a unique identifier of a Configuration
           Domain. It is used to identify the Configuration Domain a CUC
           belongs to.";
        reference
          "46.2.2.1 of IEEE Std 802.1Qdj-2023";
      }
      leaf cnc-enabled {
        type boolean;
        default "false";
        description
          "cnc-enabled is used to enable or disable the CNC functionality
           of a station capable of acting as a CNC. If this object is set
           to TRUE the CNC functionality is enabled. If it is set to FALSE
           the CNC functionality is disabled.";
        reference
          "46.2.2.3 of IEEE Std 802.1Qdj-2023";
      }
      list cuc {
        key "cuc-id";
        description
          "List of CUCs.

           This list exists so Streams can be associated with the CUC that
           initially requested them and can be used to restrict access to
           Streams, e.g., by using standard mechanisms as described in RFC
           8341.";
        leaf cuc-id {
          type string;
          description
            "The CUC ID is a unique identifier of a CUC. It is used to
             identify the CUC that a Stream belongs to, i.e., that
             requested the creation of a Stream.";
          reference
            "46.2.2.2 of IEEE Std 802.1Qdj-2023";
        }
        list stream {
          key "stream-id";
          description
            "List of Streams.

             Each Stream consists of a Stream ID, a request container, and
             a configuration container.

             In the fully centralized model of TSN configuration, the
             Stream ID and request originate from the CUC and is delivered
             to the CNC, while the configuration originates from the CNC
             and is delivered to the CUC.";
          leaf stream-id {
            type tsn:stream-id-type;
            description
              "The Stream ID is a unique identifier of a Stream request
               and corresponding configuration. It is used to associate a
               CUC’s Stream request with a CNC’s corresponding response.";
          }
          leaf stream-status {
            type enumeration {
              enum planned {
                value 0;
                description
                  "The Stream has been requested but has not yet been
                   configured by the CNC.";
              }
              enum configured {
                value 1;
                description
                  "The Stream has been computed and configured by the
                   CNC.";
              }
              enum modified {
                value 2;
                description
                  "The Stream has been configured but Stream parameters
                   have been modified after configuration.";
              }
            }
            config false;
            description
              "The stream-status indicates what status the Stream has in
               the CNC.";
            reference
              "46.2.3.8 of IEEE Std 802.1Qdj-2023";
          }
          container talker {
            description
              "The Talker container contains: - Talker’s behavior for
               Stream (how/when transmitted) - Talker’s requirements from
               the network - TSN capabilities of the Talker’s
               interface(s).";
            uses tsn:group-talker;
            uses tsn:group-status-talker-listener {
              refine "accumulated-latency" {
                config false;
              }
              refine "interface-configuration" {
                config false;
              }
            }
          }
          list listener {
            key "index";
            description
              "Each Listener list entry contains: - Listener’s
               requirements from the network - TSN capabilities of the
               Listener’s interface(s).";
            leaf index {
              type uint32;
              description
                "This index is provided in order to provide a unique key
                 per list entry.";
            }
            uses tsn:group-listener;
            uses tsn:group-status-talker-listener {
              refine "accumulated-latency" {
                config false;
              }
              refine "interface-configuration" {
                config false;
              }
            }
          }
          uses tsn:group-status-stream {
            refine "status-info" {
              config false;
            }
            refine "failed-interfaces" {
              config false;
            }
          }
        }
        action remove_streams {
          description
            "Removes the Streams with the ids provided in the stream-id
             list.";
          reference
            "46.2.8.1 of IEEE Std 802.1Qdj-2023";
          input {
            list stream-list {
              key "stream-id";
              description
                "List of stream-ids that are used to identify the Streams
                 that are requested to be removed.";
              leaf stream-id {
                type tsn:stream-id-type;
                description
                  "Unique identifier that is used to request a Stream
                   that is to be removed from the configuration.";
              }
            }
          }
          output {
            leaf result {
              type string;
              description
                "Returns status information indicating if Stream removal
                 has been successfully started.";
            }
          }
        }
      }
    }
  }

  rpc compute_streams {
    description
      "Starts computation of path and resource allocation for one or more
       Stream. The Streams that are included in the computation are the
       ones that have their domain-id, cuc-id, and stream-id provided.
       This RPC can be applied to compute new Streams as well as recompute
       Streams that have been modified.";
    input {
      list domain {
        key "domain-id";
        description
          "List of Configuration Domains.

           This list exists so CUCs can be associated with the
           Configuration Domain they are located in.";
        reference
          "46.2.7.1 of IEEE Std 802.1Qdj-2023";
        leaf domain-id {
          type leafref {
            path "/tsn-uni/domain/domain-id";
          }
          description
            "A unique identifier of a Configuration Domain. It is used to
             identify the Configuration Domain a CUC belongs to.";
        }
        list cuc {
          key "cuc-id";
          description
            "List of CUCs.

             This list exists so Streams can be associated with the CUC
             that initially requested them.";
          leaf cuc-id {
            type leafref {
              path "/tsn-uni/domain/cuc/cuc-id";
            }
            description
              "A unique identifier of a CNC. It is used to identify the
               CUC that a Streams belong to, i.e., that requested the
               creation of a Stream.";
          }
          list stream-list {
            key "stream-id";
            description
              "List of stream-ids that are used to identify the Streams
               that are requested to be computed and configured.";
            leaf stream-id {
              type leafref {
                path "/tsn-uni/domain/cuc/stream/stream-id";
              }
              description
                "Unique identifier that is used to request a Stream that
                 is to be computed and configured.";
            }
          }
        }
      }
    }
    output {
      leaf result {
        type string;
        description
          "Only returns status information indicating if the computation
           has been started. It does not return status information on the
           success or failure of the actual Stream computation. A
           notifcation can be used to inform the caller of this RPC on the
           results of Stream computation after the computation has
           finished.";
      }
    }
  }

  rpc compute_planned_and_modified_streams {
    description
      "Starts computation of path and resource allocation for all Streams
       that are in the domain provided by domain-id and are associated
       with the CUC provided by cuc-id, and that have not been computed
       (i.e., that have a Stream status of planned or modified.";
    reference
      "46.2.7.2 of IEEE Std 802.1Qdj-2023";
    input {
      list domain {
        key "domain-id";
        description
          "List of Configuration Domains.

           This list exists so CUCs can be associated with the
           Configuration Domain they are located in.";
        leaf domain-id {
          type string;
          description
            "A unique identifier of a Configuration Domain. It is used to
             identify the Configuration Domain a CUC belongs to.";
        }
        list cuc {
          key "cuc-id";
          description
            "List of CUCs.

             This list exists so Streams can be associated with the CUC
             that initially requested them.";
          leaf cuc-id {
            type string;
            description
              "A unique identifier of a CNC. It is used to identify the
               CUC that a Streams belong to, i.e., that requested the
               creation of a Stream.";
          }
        }
      }
    }
    output {
      leaf result {
        type string;
        description
          "Only returns status information indicating if the computation
           has been started. It does not return status information on the
           success or failure of the actual Stream computation. A
           notifcation can be used to inform the caller of this RPC on the
           results of Stream computation after the computation has
           finished.";
      }
    }
  }

  rpc compute_all_streams {
    description
      "Starts computation of path and resource allocation for all Streams
       that are in the domain provided by domain-id and are associated
       with the CUC provided by cuc-id.";
    reference
      "46.2.7.3 of IEEE Std 802.1Qdj-2023";
    input {
      list domain {
        key "domain-id";
        description
          "List of Configuration Domains.

           This list exists so CUCs can be associated with the
           Configuration Domain they are located in.";
        leaf domain-id {
          type string;
          description
            "A unique identifier of a Configuration Domain. It is used to
             identify the Configuration Domain a CUC belongs to.";
        }
        list cuc {
          key "cuc-id";
          description
            "List of CUCs.

             This list exists so Streams can be associated with the CUC
             that initially requested them.";
          leaf cuc-id {
            type string;
            description
              "A unique identifier of a CNC. It is used to identify the
               CUC that a Streams belong to, i.e., that requested the
               creation of a Stream.";
          }
        }
      }
    }
    output {
      leaf result {
        type string;
        description
          "Only returns status information indicating if the computation
           has been started. It does not return status information on the
           success or failure of the actual Stream computation. A
           notifcation can be used to inform the caller of this RPC on the
           results of Stream computation after the computation has
           finished.";
      }
    }
  }

  rpc request_domain_id {
    description
      "Returns the DomainId of the Configuration Domain that the
       requesting CUC belongs to.";
    reference
      "46.2.7.4 of IEEE Std 802.1Qdj-2023";
    input {
      leaf cuc-id {
        type string;
        description
          "A unique identifier of a CNC. It is used to identify the CUC,
           allowing the CNC to return the DomainId this CUC belongs to.";
      }
    }
    output {
      leaf result {
        type string;
        description
          "Returns the DomainId of the Configuration Domain that the
           requesting CUC belongs to.";
      }
    }
  }

  rpc request_free_stream_id {
    description
      "Returns a free StreamId available for the Configuration Domain
       identified by the DomainId.";
    reference
      "46.2.7.5 of IEEE Std 802.1Qdj-2023";
    input {
      leaf domain-id {
        type string;
        description
          "A unique identifier of a Configuration Domain. It is used to
           identify the Configuration Domain a CUC belongs to.";
      }
      leaf cuc-id {
        type string;
        description
          "A unique identifier of a CNC. It is used to identify the CUC,
           allowing the CNC to return the DomainId this CUC belongs to.";
      }
    }
    output {
      leaf result {
        type string;
        description
          "Returns a free StreamId available for the Configuration Domain
           identified by the DomainId.";
      }
    }
  }

  notification compute_streams_completed {
    description
      "Notifies the caller of an RPC or action that initiated the
       computation of one or multiple Streams, that the computation is
       complete. It also returns information on the success or failure for
       each of the Streams in the computation.";
    reference
      "46.2.9.1 of IEEE Std 802.1Qdj-2023";
    list domain {
      key "domain-id";
      description
        "List of Configuration Domains.

         This list exists so CUCs can be associated with the Configuration
         Domain they are located in.";
      leaf domain-id {
        type string;
        description
          "A unique identifier of a Configuration Domain. It is used to
           identify the Configuration Domain a CUC belongs to.";
      }
      list cuc {
        key "cuc-id";
        description
          "List of CUCs.

           This list exists so Streams can be associated with the CUC that
           initially requested them.";
        leaf cuc-id {
          type string;
          description
            "A unique identifier of a CNC. It is used to identify the CUC
             that a Stream belongs to, i.e., that requested the creation
             of a Stream.";
        }
        list stream {
          key "stream-id";
          description
            "List of Streams.

             Each Stream consists of a Stream ID, a request container, and
             a configuration container.

             In the fully centralized model of TSN configuration, the
             Stream ID and request originate from the CUC and is delivered
             to the CNC, while the configuration originates from the CNC
             and is delivered to the CUC.";
          reference
            "46.2.3 of IEEE Std 802.1Qdj-2023";
          leaf stream-id {
            type tsn:stream-id-type;
            description
              "The Stream ID is a unique identifier of a Stream request
               and corresponding configuration. It is used to associate a
               CUC’s Stream request with a CNC’s corresponding response.";
          }
          leaf failure-code {
            type uint8;
            description
              "A code that indicates if the computation for the Stream
               was successful (0) or not. In the case of a failure a code
               is returned to indicate what kind of failure occurred.";
          }
        }
      }
    }
  }

  notification configure_streams_completed {
    description
      "Notifies the caller of an RPC or action that initiated the
       computation of one or multiple Streams, that the computation and
       configuration is complete. It also returns information on the
       success or failure for each of the Streams in the computation and
       configuration.";
    reference
      "46.2.9.2 of IEEE Std 802.1Qdj-2023";
    list domain {
      key "domain-id";
      description
        "List of Configuration Domains.

         This list exists so CUCs can be associated with the Configuration
         Domain they are located in.";
      leaf domain-id {
        type string;
        description
          "A unique identifier of a Configuration Domain. It is used to
           identify the Configuration Domain a CUC belongs to.";
      }
      list cuc {
        key "cuc-id";
        description
          "List of CUCs.

           This list exists so Streams can be associated with the CUC that
           initially requested them.";
        leaf cuc-id {
          type string;
          description
            "A unique identifier of a CNC. It is used to identify the CUC
             that a Streams belong to, i.e., that requested the creation
             of a Stream.";
        }
        list stream {
          key "stream-id";
          description
            "List of Streams.

             Each Stream consists of a Stream ID, a request container, and
             a configuration container.

             In the fully centralized model of TSN configuration, the
             Stream ID and request originate from the CUC and is delivered
             to the CNC, while the configuration originates from the CNC
             and is delivered to the CUC.";
          reference
            "46.2.3 of IEEE Std 802.1Qdj-2023";
          leaf stream-id {
            type tsn:stream-id-type;
            description
              "The Stream ID is a unique identifier of a Stream request
               and corresponding configuration. It is used to associate a
               CUC’s Stream request with a CNC’s corresponding response.";
          }
          leaf failure-code {
            type uint8;
            description
              "A code that indicates if the computation and configuration
               for the Stream was successful (0) or not. In the case of a
               failure a code is returned to indicate what kind of failure
               occurred.";
          }
        }
      }
    }
  }

  notification remove_streams_completed {
    description
      "Notifies the caller of an RPC or action that initiated the removal
       of one or multiple Streams, that the removal is complete. It also
       returns information on the success or failure for each of the
       Streams in the removal request.";
    reference
      "46.2.9.3 of IEEE Std 802.1Qdj-2023";
    list domain {
      key "domain-id";
      description
        "List of Configuration Domains.

         This list exists so CUCs can be associated with the Configuration
         Domain they are located in.";
      leaf domain-id {
        type string;
        description
          "A unique identifier of a Configuration Domain. It is used to
           identify the Configuration Domain a CUC belongs to.";
      }
      list cuc {
        key "cuc-id";
        description
          "List of CUCs.

           This list exists so Streams can be associated with the CUC that
           initially requested them.";
        leaf cuc-id {
          type string;
          description
            "A unique identifier of a CNC. It is used to identify the CUC
             that a Streams belong to, i.e., that requested the creation
             of a Stream.";
        }
        list stream {
          key "stream-id";
          description
            "List of Streams.

             Each Stream consists of a Stream ID, a request container, and
             a configuration container.

             In the fully centralized model of TSN configuration, the
             Stream ID and request originate from the CUC and is delivered
             to the CNC, while the configuration originates from the CNC
             and is delivered to the CUC.";
          reference
            "46.2.3 of IEEE Std 802.1Qdj-2023";
          leaf stream-id {
            type tsn:stream-id-type;
            description
              "The Stream ID is a unique identifier of a Stream request
               and corresponding configuration. It is used to associate a
               CUC’s Stream request with a CNC’s corresponding response.";
          }
          leaf failure-code {
            type uint8;
            description
              "A code that indicates if the removal of the Stream was
               successful (0) or unsuccessful (1).";
          }
        }
      }
    }
  }
}
